# 01_CRS

## #1: Overview (Informational)
The system is to control at least two sets of traffic lights and a set of boom gates for a busy train line at intersections as given in the following diagram. This is the minimum level of complexity to achieve a Pass grade.

## #2: Traffic Corridor Example (Informational)
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
## #3: Layout (Informational)
In the example above, there is a road (R3 going from top-left to bottom-right of diagram, but it actually goes in a North-South direction) along which there are two road intersections (I1 and I2) and a railway crossing (X1). The crossing roads at each intersection (R1 and R2) each go in an East-West direction.

## #4: Intersection traffic (Functional)
All roads (East-West and North-South) carry two-way traffic, have two lanes in each direction, may have turn lanes at each intersection (I1 and I2),

## #5: Pedestrian crossing (Functional)
and may have pedestrian crossing lights at each intersection (I1 and I2)

## #6: Traffic flow (Functional)
R1 and R3 are major roads with a high level of traffic, whereas R2 (whilst still a major road) has only a moderate level of traffic.

## #7: Train boom and lights (Functional)
The railway crossing has boom gates and red flashing lights that operate whenever a train crosses the road.

## #8: Train schedule (Informational)
There are two train lines, one for trains travelling each direction. The time between trains varies from frequent (as little as 2 minutes apart) at peak hour to infrequent (about every 20 minutes) at night (~10:00pm) - All night trains run on Friday and Saturday nights.

## #9: Traffic light->train sensing (Functional)
The traffic light system can sense the state of the railway crossing (but has no control over it).

## #10: Train stop if issue (Functional)
The train should receive a red light if there are any issues with the boom gates – thus indicating an error which should be reported to the control room.

## #11: Local controller (Functional)
Each intersection/pedestrian crossing has a local controller for the lights at the intersection which operate continuously (except for hardware failure).

## #12: Central Controller (Functional)
Each local controller also communicates with a central controller (but should continue to operate if either communication link fails or the central controller goes offline).

## #13: Intrersection controllers (Functional)
The two intersection controllers (I1 and I2) operate independently, however can receive commands from a central controller to determine the light sequence pattern that they should follow for different times of the day.
Note may have more or less intersections depending on selected corridor

## #14: TL Red if train (Functional)
However, both intersections must sense the state of the railway crossing (X1) and sequence their set of lights for R3 to red when a train is crossing at X1, whist still trying to accommodate traffic on all three roads.

## #15: ped button + light (Functional)
The support for pedestrian buttons and lights should also be considered for grades above a Credit level.

## #16: Central control room (Functional)
There is a central control room with a central controller, which monitors the traffic lights and displays the status, and light settings received from the individual intersections.

## #17: Local->Central controller communication (Functional)
Therefore, each local controller will send a status message to the central controller whenever any of the lights at that intersection change state, and act on any commands received from the central controller.

## #18: Central controller does not control individual lights (Functional)
Note that the central controller does not directly control the individual lights at an intersection - that is always done by the local controller and must be maintained even in the event that the controller cannot communicate with an intersection of another controller.

## #19: Train line controller (Functional)
A full implementation would also have a train line controller that handles the communication link between the traffic central controller and the train lines.

## #20: Modelling your design on a real intersection (Functional)
Below is an example intersection in Melbourne which might help with breaking down the problem. You should at least attempt to base your design on a real intersection - this may help with you formulating your justifications and requirements. You can include tram line signalling if needed too.

## #21: Traffic flow (Informational)
By measuring the distance between the traffic light intersections and train crossing you can start to determine the timing requirements and traffic light sequences that will be needed in-order to clear the intersections and avoid traffic backing up.

## #22: Assumtions (Informational)
By making some realistic assumptions, the side roads can be eliminated from the design as they are not important. As an example, during peak time with trains approaching from both sides, it can take between 3 to 10 minutes to follow the path outlined by the red arrows if there are pedestrians trying to cross Glenroy Rd or Hartington St.

## #23: Pick our own intersection (Informational)
Please note: The example intersection is only provided to illustrate a real-life example. You should choose your own model intersection as of 2021, this rail crossing was removed by the Victorian government.

## #24: Possible light sequence patterns (Functional)
Possible light sequence patterns for each intersection local controller (set by a command from the central controller) include:
• Fixed timing – commonly used during peak hours
• Sensor driven (react to local car sensors & any pedestrian buttons) – commonly used in off-peak times.
• Advanced: updateable sequence structure or timing requests from central controller.

## #25: Central controller operation (Functional)
The central controller may send a command to change the sequence a few times a day (e.g. depending on the time of day).
Operators in the central control room will occasionally send commands to the intersections, boom gate control and train approach signals system.

## #26: Intersection image (Informational)
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
## #27: Override commands (Functional)
The central control room may also initiate override commands that are sent to the individual intersections to deal with exceptional situations (e.g. to provide a clear path for a visiting dignitary).

## #28: Demonstration exceptions (Informational)
At all times the lights at each intersection must exhibit the “expected” behaviour of real traffic lights, however the timing between state changes may be speed up for practical and demonstration reasons.

## #29: Variation in solution (Informational)
These specifications do not describe every possible feature of the intersections, leaving some room for variations in solutions (e.g. pedestrian lights, right turn arrows etc at the intersections).

## #30: Simulation (Functional)
You will need to simulate sensor events in your implementation e.g. using key presses (this will require an additional process or thread to wait for the key presses).

## #31: Interacting with system for demonstration examples (Functional)
You are free to use console input, the provided Beaglebone LCD/keypads in the lab (if available), or GPIO developed on your own Raspberry Pi 4, DE10-nano or Beaglebone targets. Otherwise, you would need to use the consoles or Telnet sessions to multiple _x86 QNX Target VMs, depending on the complexity of the solution your team is aiming to achieve. See the accompanying project rubric to get an idea of the different levels of complexity that are expected for different grade levels.

## #32: Number of node expectation (Functional)
Note that a demonstration using only three QNX node will attract a Pass to Credit level (e.g. I1 running on one computer, I2 running on a second node and a third QNX node acting as the central controller or train controller) as define in the rubric. In all cases, it is expected that your solution will have three or more QNX nodes with separate processes/threads on each node to handle the features such as pedestrian / sensor inputs and/or communication links, with another process used to display the traffic light states.

## #33: Interface examples (Informational)
You are not required to have a graphical user interface; it is sufficient to display the state of each intersection by writing simple text messages to a terminal window or via and LCD attached to the Beaglebone or a customised hardware display on your own target/s. You are encouraged to use the provided Beaglebone LEDs and/or LCD to display states (if lab hardware is made available) or your own interface hardware.

## #34: Persistent file system use (Informational)
You can also make use of the persistent file system on some targets (i.e. Beaglebone supports this feature) under the /fs directory. You can store test vectors or debug information for offline analysis, or any other feature you think is suitable.

## #35: Free to make reasonable assumtions (Informational)
You are free to make any reasonable assumptions necessary to proceed with the design as long as you outline them upfront, however it is a good idea to justify your decision on a simplified real-life traffic light intersection.

## #36: Guide for HD (Informational)
As a rough guide, according to the rubric, a group of 4 students aiming for High Distinction grade level would propose and deliver a system using 5 or more QNX nodes with custom hardware with IPC implemented with native message passing techniques and a host of features such as: updateable pattern sequencing; external sensors and displays; custom hardware; separate nodes for each intersection and controller; appropriate synchronization primitives; timers and software/hardware interrupts; excellent code management and commenting; and host of well thought-out features and well timed demonstration/presentation. Obviously, there is room for movement as a given team might focus more highly on certain features over other features or implementation methods.

## #39: Justifications

### #40

### #41
