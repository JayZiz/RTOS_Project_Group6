# 02_SYSRS

## #5: The system must include a train crossing between intersections with boom gates and flashing lights. (Functional)

### #6: The system must detect approaching trains using train sensors at the crossing. (Functional)

### #10: Train detection must trigger boom‑gate closure and train warning lights. (Functional)

### #11: Train‑crossing behaviour must operate solely based on train sensor input. (Functional)

### #33: Train must not be allowed to cross in case of issue with controller (Functional)

#### #34: In this case it must send fault code to cental node (Functional)

### #38: The train crossing must have its own controller (Functional)

## #14: The system must coordinate intersections and the train crossing to prevent excessive traffic buildup along the corridor. (Functional)

## #18: The system must operate across multiple distributed nodes (minimum five). (Functional)

### #19: Nodes must communicate using message‑based interactions. (Functional)

## #20: The system must support any suitable output hardware (LEDs, LCD, console, etc.). (Functional)

## #21: The system must meet real‑time responsiveness requirements appropriate for corridor safety. (Functional)

## #22: The system must include moderate fault‑tolerance with safe fallback states. (Functional)

## #23: The system must support node restart behaviour during faults. (Functional)

## #24: The system must ensure the corridor remains in a safe state during faults. (Functional)

## #26: The project must include a comprehensive test plan. (Functional)

## #29: The system must model a real Melbourne road corridor consisting of multiple intersections. (Functional)

### #2: Each intersection must include standard Australian traffic lights. (Functional)

### #3: Each intersection must include right‑turn arrows. (Functional)

### #4: Each intersection must include pedestrian crossings. (Functional)

### #7: Each intersection must detect vehicle presence for straight‑through lanes at each intersection. (Functional)

### #8: Each intersection must detect vehicle presence for right‑turn lanes at each intersection. (Functional)

### #9: Each intersection must detect pedestrian button presses. (Functional)

### #12: Intersection traffic‑light behaviour must adapt dynamically based on vehicle sensors. (Functional)

### #13: Intersection traffic‑light behaviour must adapt dynamically based on pedestrian requests. (Functional)

### #35: Each intersection must have it own local controller (Functional)

## #30: Justifications

### #31

### #32

## #36: The control room must display current status of the corridor (Functional)

### #16: The system must include a central control node that can adjust intersection phases dynamically. (Functional)

### #37: Cental control shall not have control over individual lights (Functional)

### #39: The central control node must have override commands for intersections (Functional)
